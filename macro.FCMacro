# Copyright 2015 Matthew Rogge and Michael Uttmark
# 
# This file is part of Retr3d.
# 
# Retr3d is free software: you can redistribute it and/or modify
# it under the terms of the GNU General Public License as published by
# the Free Software Foundation, either version 3 of the License, or
# (at your option) any later version.
# 
# Retr3d is distributed in the hope that it will be useful,
# but WITHOUT ANY WARRANTY; without even the implied warranty of
# MERCHANTABILITY or FITNESS FOR A PARTICULAR PURPOSE.  See the
# GNU General Public License for more details.
# 
# You should have received a copy of the GNU General Public License
# along with Retr3d.  If not, see <http://www.gnu.org/licenses/>.

import sys, os, subprocess
from PySide import QtGui

retr3d_path = QtGui.QFileDialog.getExistingDirectory(None,"Please indicate the location of your Retr3D folder")
output_path = QtGui.QFileDialog.getExistingDirectory(None,"Now please choose a folder to save output files")

if retr3d_path and output_path:
    sys.path.append(retr3d_path)
    import globalVars as gv
    gv.printerDir = output_path + os.sep
    import makePrinter
else:
    print "Aborting."
